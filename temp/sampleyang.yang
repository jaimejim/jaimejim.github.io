<CODE BEGINS>
module ietf-yang-xxx {

  yang-version 1;

  namespace
      "urn:ietf:params:xml:ns:yang:ietf-yang-xxx";

  prefix xxx;

  organization
    "IPSO";

  contact
     "WG Web:   http://tools.ietf.org/wg/roll/
     WG List:  mailto:roll@ietf.org

     WG Chair: Peter van der Stok
               mailto:consultancy@vanderstok.org

     WG Chair: Ines Robles
               mailto:maria.ines.robles@ericsson.com

     Editor:   Peter van der Stok
               mailto:consultancy@vanderstok.org";

  description
    "This module contains information about the operation of the MPL protocol.

     Copyright (c) 2016 IETF Trust and the persons identified as
     authors of the code.  All rights reserved.

     Redistribution and use in source and binary forms, with or

     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

revision "2016-07-19" {
      description "Initial revision.";
      reference
        "I-D:draft-vanderstok-roll-mpl-yang: A YANG model for Multicast Protocol for Low power and lossy Networks (MPL)";
    }

    list xxx {
      description
      //TODO: Check this...
        "This the set of instances that a device has";
        key instance_number;
            leaf instance_number {
            type uint16;
            description
             "the number of the instance";
            }
            // YANG does not have float.
            leaf sensor_value {
            type decimal64;
            description
             "Last or Current Measured Value from the Sensor";
            }

            leaf 5700 {
            type decimal64;
            description
             "Sensor Value: Last or Current Measured Value from the Sensor";
            }


       }  // list xxx
} // module ietf-yang-xxx

<CODE ENDS>
